(defun c:CHGSELATTRIB (/ ss blkname atttag newcontent ent attvals attval)
  (if (setq ss (ssget "_X" '((0 . "INSERT"))))
    (progn
      (setq ent (ssname ss 0))
      (setq blkname (cdr (assoc 2 (entget ent))))
      (if (and blkname (not (getvar 'pickadd)))
        (setq atttag (getstring "\nEnter the tag of the attribute: "))
      )
      (setq newcontent (getstring "\nEnter the new content: "))
      (setq attvals (mapcar 'cdr (vl-remove-if-not '(lambda (x) (equal (cdr (assoc 2 x)) atttag)) (entget ent))))
      (if (not (null attvals))
        (progn
          (setq attval (car attvals))
          (setq attval (subst newcontent (cdr attval) attval))
          (setq attval (cons 1 attval))
          (setq ent (subst attval (assoc 1 (entget ent)) (entget ent)))
          (entmod ent)
          (princ "\nAttribute updated successfully.")
        )
        (princ "\nAttribute not found.")
      )
    )
    (princ "\nNo blocks selected.")
  )
  (princ)
)
