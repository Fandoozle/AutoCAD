(DEFUN C:RunScripts ()
  (IF (FINDFILE "C:\Users\jschnees\Desktop\Scripts\ALLOWEXPLODEBLOCKS.lsp"")
    (command "SCRIPT" "C:\Users\jschnees\Desktop\Scripts\ALLOWEXPLODEBLOCKS.lsp")
  )
  (IF (FINDFILE "Q:\master\Setup\Setup Scripts\changeLayerColors")
    (command "SCRIPT" "Q:\master\Setup\Setup Scripts\changeLayerColors")
  )
  (IF (FINDFILE "C:\Users\jschnees\Desktop\Scripts\NOZ.LSP")
    (command "SCRIPT" "C:\Users\jschnees\Desktop\Scripts\NOZ.LSP")
  )
)
