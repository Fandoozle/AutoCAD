;Jeff Clark     last modified 10/08/03
;Changes "Z" elevations of LINES and ARCS and POLYLINES to "0.0";
;
(defun C:NOZ (/ SS1 SS2 CNT1 CNT2 CNT3 ENT ED A B C D E F)

 (setq SS1 (ssget "X" '((0 . "line"))))
 (setq CNT1 (sslength ss1))
 (setq CNT2 0)
 (setq CNT3 0)
 (setq counter 0)
 (while (< CNT2 CNT1)
  (setq ENT (ssname  SS1 CNT3))
  (setq ED (entget ENT))
  (setq A (cdr (assoc 10 ED)))
  (setq B (subst 0.0 (caddr A) A))
  (setq ED (subst (cons 10 B) (assoc 10 ED) ED))
  (entmod ED)
  (setq C (cdr (assoc 11 ED)))
  (setq D (subst 0.0 (caddr C) C))
  (setq ED (subst (cons 11 D) (assoc 11 ED) ED))
  (entmod ED)
  (entupd ENT)
  (setq CNT2 (+ CNT2 1))
  (setq CNT3 (+ CNT3 1))
  (setq counter (+ counter 1))
 )
 (setq SS2 (ssget "X" '((0 . "arc"))))
 (setq CNT1 (sslength SS2))
 (setq CNT2 0)
 (setq CNT3 0)
 (while (< CNT2 CNT1)
  (setq ENT (ssname SS2 CNT3))
  (setq ED (entget ENT))
  (setq E (cdr (assoc 10 ED)))
  (setq F (subst 0.0 (caddr E) E))
  (setq ED (subst (cons 10 F) (assoc 10 ED) ED))
  (entmod ED)
  (entupd ENT)
  (setq CNT2 (+ CNT2 1))
  (setq CNT3 (+ CNT3 1))
  (setq counter (+ counter 1))
 )
 (setq SS2 (ssget "X" '((0 . "LWPOLYLINE"))))
 (setq CNT1 (sslength SS2))
 (setq CNT2 0)
 (setq CNT3 0)
 (while (< CNT2 CNT1)
  (setq ENT (ssname SS2 CNT3))
  (setq ED (entget ENT))
  (setq E (assoc 38 ED))
  (setq ED (subst (cons 38 0.0) (assoc 38 ED) ED))
  (entmod ED)
  (entupd ENT)
  (setq CNT2 (+ CNT2 1))
  (setq CNT3 (+ CNT3 1))
  (setq counter (+ counter 1))
 )
 (prompt (strcat (rtos counter 2 0) " Entities Checked or Changed"))
 (princ)
)
